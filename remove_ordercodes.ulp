#require 6.0500 //Version 6.5.0

#usage 	"<b>Bestellnummern entfernen</b>"
		"<p>"
		"Entfernt die durch das BOM-Script eingefügten Bestellnummern"
		"<p>"
    

//providers
string PROVIDER_NAMES[] = {"FARNELL","REICHELT","DIGIKEY","WUERTH","MINICIRCUITS","RS"}; ///Only these attributes are important; all other will be ignored without warning
int PROVIDER_COUNT	= 6;

string msg;
string exit_cmd;

schematic(schem){
	schem.parts(part){
    if( (part.device.package) && (part.device.package.name != "BESTELLTEILE") ){
  		part.attributes(attribute){
        for(int i=0;i<PROVIDER_COUNT;i++){
          if(PROVIDER_NAMES[i] == attribute.name){
            //found an ordercode-attribute -> delete it
/*
sprintf(msg, "name: %s", part.name);
if(dlgMessageBox(msg, "Ok", "Abbruch") != 0){
  exit(exit_cmd);
}
*/
            exit_cmd += "ATTRIBUTE " + part.name + " " + attribute.name + " DELETE; ";
          }
        }
      }
    }
  }
}

exit(exit_cmd);
